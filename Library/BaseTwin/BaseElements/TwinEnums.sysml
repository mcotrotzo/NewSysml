library package TwinEnumLibrary{
    public enum def TimeUnit{
        MICROSECOND;
        MILLISECOND;
        HOUR;
        SECOND;
        MINUTE;
        DAY;
        YEAR;
    }

    public enum def ORDER_BY {
        enum ASCENDING;
        enum DESCENDING;
    }

}
